-- *****************************************************************
-- DELLEMC-OS10-VRRP-MIB
--
--
-- Copyright (c) 2023 by Dell Inc.
-- All rights reserved.
-- *****************************************************************

	DELLEMC-OS10-VRRP-MIB DEFINITIONS ::= BEGIN
    --  This module provides authoritative definitions for Dell Networking OS10
    --  VRRP MIB.
    --
    --  This module will be extended, as needed.
    --

    IMPORTS

	MODULE-IDENTITY, OBJECT-TYPE, NOTIFICATION-TYPE,
        Counter32, Gauge32, Unsigned32
            FROM SNMPv2-SMI
	os10Experiment
	    	FROM DELLEMC-OS10-SMI-MIB
        InetAddressType, InetAddress, InetPortNumber,
        InetAutonomousSystemNumber, InetAddressPrefixLength
        	FROM INET-ADDRESS-MIB
        TruthValue, RowPointer, TimeStamp, DisplayString, TEXTUAL-CONVENTION
        	FROM SNMPv2-TC
        MODULE-COMPLIANCE, OBJECT-GROUP, NOTIFICATION-GROUP
            FROM SNMPv2-CONF
        SnmpAdminString
            FROM SNMP-FRAMEWORK-MIB;

        os10VrrpMib MODULE-IDENTITY
            LAST-UPDATED "202303311800Z"
            ORGANIZATION "Dell"
            CONTACT-INFO "http://www.dell.com/support"
            DESCRIPTION
                    "This MIB updates and replaces the vrrpNotifications part of 
					VRRP MIB defined in RFC 3768."
            ::= { os10Experiment 3 }


    -- Top level components of this MIB module

    -- Notifications
    os10vrrpV2Notifications OBJECT IDENTIFIER ::= { os10VrrpMib 0 }
    os10vrrpV3Notifications OBJECT IDENTIFIER ::= { os10VrrpMib 1 }

    -- Objects
    os10vrrpObjects   OBJECT IDENTIFIER ::= { os10VrrpMib 2 }
    os10vrrpV3Objects OBJECT IDENTIFIER ::= { os10VrrpMib 3 }

    os10VrrpActiveIpAddr OBJECT-TYPE
        SYNTAX     DisplayString (SIZE (0..32))
        MAX-ACCESS read-only
        STATUS     current
        DESCRIPTION
               "The active router's real IP address. Active router
               would set this address to vrrpActiveIpAddr
               while transitioning to active state. For backup
               routers, this is the IP address listed as the source in
               VRRP advertisement last received by this virtual
               router."
        ::= { os10vrrpObjects 1 }
               
    os10VrrpPacketSrc OBJECT-TYPE
        SYNTAX     DisplayString (SIZE (0..32))
        MAX-ACCESS read-only
        STATUS     current
        DESCRIPTION
               "The IP address of an inbound VRRP packet. Used by
               os10VrrpAuthFailure trap."
        ::= { os10vrrpObjects 2 }

    os10VrrpAuthErrorType OBJECT-TYPE
        SYNTAX     INTEGER {
           invalidAuthType  (1),
           authTypeMismatch (2),
           authFailure      (3)
        }
        MAX-ACCESS read-only
        STATUS     current
        DESCRIPTION
               "Potential types of configuration conflicts.
               Used by os10VrrpAuthFailure trap." 	
        ::= { os10vrrpObjects 3 }

    os10VrrpVrfName OBJECT-TYPE
        SYNTAX     DisplayString (SIZE (0..32))
        MAX-ACCESS read-only
        STATUS     current
        DESCRIPTION
            "Name of the VRF the VRRP group belongs to."
        ::= { os10vrrpObjects 4 }

    os10VrrpAuthErrorTypeStr OBJECT-TYPE
        SYNTAX     DisplayString (SIZE (0..32))
        MAX-ACCESS read-only
        STATUS     current
        DESCRIPTION
            "A string representation for os10VrrpAuthFailure reason."
        ::= { os10vrrpObjects 5 }

    os10VrrpV3ActiveIpAddr OBJECT-TYPE
        SYNTAX     DisplayString (SIZE (0..128))
        MAX-ACCESS read-only
        STATUS     current
        DESCRIPTION
               "The active router's real IP address. Active router
               would set this address to vrrpActiveIpAddr
               while transitioning to active state. For backup
               routers, this is the IP address listed as the source in
               VRRP advertisement last received by this virtual
               router."
        ::= { os10vrrpV3Objects 1 }

    os10VrrpNewActiveReason OBJECT-TYPE
        SYNTAX     INTEGER {
           notActive        (0),
           priority         (1),
           preempted        (2),
           activeNoResponse (3)
        }
        MAX-ACCESS read-only
        STATUS     current
        DESCRIPTION
           "This indicates the reason for the virtual router to
           transition to active state.  If the virtual router
           never transitioned to active state, the value of this
           object is notActive(0).  Otherwise, this indicates the
           reason this virtual router transitioned to active
           state the last time.  Used by os10VrrpV3NewActive
           notification."
        ::= { os10vrrpV3Objects 2 }

    os10VrrpProtoErrReason OBJECT-TYPE
        SYNTAX     INTEGER {
           noError       (0),
           ipTtlError    (1),
           versionError  (2),
           checksumError (3),
           vrIdError     (4)
        }
        MAX-ACCESS read-only
        STATUS     current
        DESCRIPTION
               "This indicates the reason for the last protocol
               error.  This SHOULD be set to noError(0) when no
               protocol errors are encountered.  Used by
               os10VrrpV3ProtoError notification."
        ::= { os10vrrpV3Objects 3 }

    os10VrrpNewActiveReasonStr OBJECT-TYPE
        SYNTAX     DisplayString (SIZE (0..32))
        MAX-ACCESS read-only
        STATUS     current
        DESCRIPTION
             "A string representation for os10VrrpV3NewActive."
        ::= { os10vrrpV3Objects 4 }

    os10VrrpProtoErrReasonStr OBJECT-TYPE
        SYNTAX     DisplayString (SIZE (0..32))
        MAX-ACCESS read-only
        STATUS     current
        DESCRIPTION
            "A string representation for os10VrrpV3ProtoError."
        ::= { os10vrrpV3Objects 5 }

-- Notification Configuration

    os10VrrpNewActive NOTIFICATION-TYPE
        OBJECTS {
            os10VrrpVrfName,
            os10VrrpActiveIpAddr
        }   
        STATUS     current
        DESCRIPTION
               "The os10VrrpNewActive trap indicates that the sending agent
               has transitioned to 'Active' state."
        ::= { os10vrrpV2Notifications 1 }

    os10VrrpAuthFailure NOTIFICATION-TYPE
        OBJECTS {
            os10VrrpVrfName,
            os10VrrpPacketSrc,
            os10VrrpAuthErrorType,
            os10VrrpAuthErrorTypeStr
        }
        STATUS     current
        DESCRIPTION
               "A os10VrrpAuthFailure trap signifies that a packet has
               been received from a router whose authentication key
               or authentication type conflicts with this router's
               authentication key or authentication type. Implementation
               of this trap is optional."
        ::= { os10vrrpV2Notifications 2 }

    os10VrrpV3NewActive NOTIFICATION-TYPE
        OBJECTS {
            os10VrrpVrfName,
            os10VrrpV3ActiveIpAddr,
            os10VrrpNewActiveReason,
            os10VrrpNewActiveReasonStr
        }
        STATUS     current
        DESCRIPTION
               "The os10VrrpV3NewActive trap indicates that the sending agent
               has transitioned to 'Active' state."
        ::= { os10vrrpV3Notifications 1 }

    os10VrrpV3ProtoError NOTIFICATION-TYPE
        OBJECTS {
            os10VrrpVrfName,
            os10VrrpV3ActiveIpAddr,
            os10VrrpProtoErrReason,
            os10VrrpProtoErrReasonStr
        }
        STATUS     current
        DESCRIPTION
               "The os10VrrpV3ProtoError trap indicates that the sending agent has
               encountered the protocol error indicated by
               os10VrrpProtoErrReason."
        ::= { os10vrrpV3Notifications 2 }

 END
